MediaMessages DEFINITIONS AUTOMATIC TAGS ::= BEGIN
  IMPORTS Codec, Decoder, Dimension, Location, SequenceId FROM CommonTypes;

  Rectangle ::= SEQUENCE {
    codec Codec,
    data OCTET STRING,
    dimension Dimension OPTIONAL,
    ...
  }

  RectangleUpdate ::= SEQUENCE {
    sequenceId SequenceId,
    location Location,
    rectangle Rectangle,
    ...
  }

  FramebufferUpdate ::= SEQUENCE {
    rectangleUpdates SEQUENCE OF RectangleUpdate,
    ...
  }

  MediaKeepalive ::= SEQUENCE {
    decoder Decoder,
    ...
  }

  ServerToClientMessage ::= CHOICE {
    framebufferUpdate FramebufferUpdate,
    ...
  }

  ClientToServerMessage ::= CHOICE {
    mediaKeepalive MediaKeepalive,
    ...
  }

END
