ControlMessages DEFINITIONS AUTOMATIC TAGS ::= BEGIN
  IMPORTS
    ClientId, ClientCaps, CursorBitmap, Decoder, Dimension, DurationMs,
      HeartbeatId, Location, SemVer, SequenceId FROM CommonTypes;

  OS ::= ENUMERATED {
    linux,
    windows,
    mac,
    ...
  }

  Bitness ::= ENUMERATED {
    b32,
    b64,
    ...
  }

  Endianness ::= ENUMERATED {
    big,
    little,
    ...
  }

  Architecture ::= ENUMERATED {
    x86,
    arm,
    ...
  }

  DecoderSequencePair ::= SEQUENCE {
    decoder Decoder,
    sequenceId SequenceId
  }

  DecoderArea ::= SEQUENCE {
    decoder Decoder,
    location Location,
    dimension Dimension,
    ...
  }

  ClientInfo ::= SEQUENCE {
    version SemVer,
    buildId UTF8String,
    os OS,
    osVersion UTF8String,
    sslLibrary UTF8String,
    sslVersion UTF8String,
    bitness Bitness,
    endianness Endianness,
    architecture Architecture,
    cpuId UTF8String,
    numberOfCores INTEGER (1..MAX),
    amountOfRam UTF8String,
    displaySize Dimension,
    ...
  }

  ClientInit ::= SEQUENCE {
    tempId ClientId,
    clientInfo ClientInfo,
    clientCaps ClientCaps,
    clientHeartbeatInterval DurationMs,
    clientHeartbeatResponseInterval DurationMs,
    maxDecoderCount INTEGER(1..MAX),
    ...
  }

  ClientGoodbyeReason ::= ENUMERATED {
    userRequested,
    networkError,
    terminating,
    ...
  }

  ClientGoodbye ::= SEQUENCE {
    clientId ClientId,
    reason ClientGoodbyeReason,
    ...
  }

  HeartbeatResponse ::= SEQUENCE {
    heartbeatId HeartbeatId,
    lastSequenceIds SEQUENCE OF DecoderSequencePair,
    ...
  }

  FramebufferUpdateRequest ::= SEQUENCE {
    location Location,
    dimension Dimension,
    ...
  }

  MissedFrameReport ::= SEQUENCE {
    decoder Decoder,
    frames SEQUENCE OF SequenceId,
    ...
  }

  ClientToServerMessage ::= CHOICE {
    clientInit ClientInit,
    clientGoodbye ClientGoodbye,
    heartbeatResponse HeartbeatResponse,
    framebufferUpdateRequest FramebufferUpdateRequest,
    missedFrameReport MissedFrameReport,
    ...
  }

  ServerInit ::= SEQUENCE {
    clientId ClientId,
    serverName UTF8String,
    eventPort INTEGER(1024..65535),
    displaySize Dimension,
    cursorBitmaps SEQUENCE OF CursorBitmap OPTIONAL,
    decoderAreas SEQUENCE OF DecoderArea,
    ...
  }

  ServerGoodbyeReason ::= ENUMERATED {
    serverShuttingDown,
    networkError,
    ...
  }

  ServerGoodbye ::= SEQUENCE {
    reason ServerGoodbyeReason,
    ...
  }

  HeartbeatRequest ::= SEQUENCE {
    requestId HeartbeatId,
    ...
  }

  ServerToClientMessage ::= CHOICE {
    serverInit ServerInit,
    serverGoodbye ServerGoodbye,
    heartbeatRequest HeartbeatRequest,
    ...
  }

END
