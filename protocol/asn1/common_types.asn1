CommonTypes DEFINITIONS AUTOMATIC TAGS ::= BEGIN
  DurationMs ::= INTEGER (0..MAX)

  ClientId ::= INTEGER (0..MAX)

  SequenceId ::= INTEGER(0..MAX)

  SemVer ::= SEQUENCE {
    major INTEGER (0..MAX),
    minor INTEGER (0..MAX),
    patch INTEGER (0..MAX),
    ...
  }

  Dimension ::= SEQUENCE {
    width INTEGER (1..MAX),
    height INTEGER (1..MAX),
    ...
  }

  Location ::= SEQUENCE {
    xPosition INTEGER (0..MAX),
    yPosition INTEGER (0..MAX),
    ...
  }

  Codec ::= ENUMERATED {
    raw,
    zlib,
    ...
  }

  ClientCaps ::= SEQUENCE {
    supportedCodecs SEQUENCE OF Codec,
    ...
  }

  HeartbeatId ::= INTEGER (0..MAX)

  -- From www.freedesktop.org/wiki/Specifications/cursor-spec
  Cursor ::= ENUMERATED {
    default,
    text,
    pointer,
    help,
    progress,
    wait,
    copy,
    alias,
    no-drop,
    not-allowed,
    all-scroll,
    row-resize,
    col-resize,
    e-resize,
    ne-resize,
    nw-resize,
    n-resize,
    se-resize,
    sw-resize,
    s-resize,
    w-resize
  }

  CursorBitmap ::= SEQUENCE {
    cursor Cursor,
    data OCTET STRING
  }

  Decoder ::= SEQUENCE {
    port INTEGER(1024..65535),
    ...
  }

END
