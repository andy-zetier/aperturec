EventMessages DEFINITIONS AUTOMATIC TAGS ::= BEGIN
  IMPORTS Cursor, Dimension, Location FROM CommonTypes;

  MappedButton ::= ENUMERATED {
    left (0),
    middle (1),
    right (2),
    wheelScrollUp (3),
    wheelScrollDown (4),
    wheelScrollLeft (5),
    wheelScrollRight (6),
    back (7),
    forward (8),
    ...
  }

  Button ::= CHOICE {
    mappedButton MappedButton,
    unmappedButton INTEGER (9..255),
    ...
  }

  ButtonState ::= SEQUENCE {
    button Button,
    isDepressed BOOLEAN,
    ...
  }

  KeyEvent ::= SEQUENCE {
    down BOOLEAN,
    key INTEGER (0..MAX),
    ...
  }

  PointerEvent ::= SEQUENCE {
    buttonStates SEQUENCE OF ButtonState,
    location Location,
    cursor Cursor,
    ...
  }

  DisplayEvent ::= SEQUENCE {
    displaySize Dimension,
    ...
  }

  ClientToServerMessage ::= CHOICE {
    keyEvent KeyEvent,
    pointerEvent PointerEvent,
    displayEvent DisplayEvent,
    ...
  }

END
